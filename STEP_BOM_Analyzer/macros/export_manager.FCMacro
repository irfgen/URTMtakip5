# -*- coding: utf-8 -*-
"""
STEP BOM Analyzer - Export Manager Macro
FreeCAD Native Macro for multi-format export

This macro handles:
- HTML report generation with embedded images
- Excel workbook creation with multiple sheets
- PDF report generation (if available)
- Multi-format export coordination
- Professional report templates
"""

import FreeCAD as App
import os
import json
import csv
from datetime import datetime
import sys

# Macro Information
__title__ = "STEP BOM Analyzer - Export Manager"
__author__ = "ÜRTM Takip Ekibi"
__version__ = "3.0.0"
__date__ = "2025-09-07"

def log_message(message, level="INFO"):
    """FreeCAD Console'a mesaj yaz"""
    timestamp = datetime.now().strftime("%H:%M:%S")
    formatted_msg = f"[{timestamp}] EXPORT_MANAGER - {level}: {message}"
    
    if level == "ERROR":
        App.Console.PrintError(formatted_msg + "\n")
    elif level == "WARNING": 
        App.Console.PrintWarning(formatted_msg + "\n")
    else:
        App.Console.PrintMessage(formatted_msg + "\n")

class HTMLReportGenerator:
    """HTML BOM raporu oluşturucu"""
    
    def __init__(self, bom_data, part_images=None):
        self.bom_data = bom_data
        self.part_images = part_images or {}
        
    def generate_html_template(self):
        """Modern HTML template oluştur"""
        html_template = """
<!DOCTYPE html>
<html lang="tr">
<head>
    <meta charset="UTF-8">
    <meta name="viewport" content="width=device-width, initial-scale=1.0">
    <title>STEP BOM Analysis Report</title>
    <style>
        * {
            margin: 0;
            padding: 0;
            box-sizing: border-box;
        }
        
        body {
            font-family: 'Segoe UI', Tahoma, Geneva, Verdana, sans-serif;
            line-height: 1.6;
            color: #333;
            background-color: #f5f5f5;
        }
        
        .container {
            max-width: 1200px;
            margin: 0 auto;
            padding: 20px;
            background-color: white;
            box-shadow: 0 0 10px rgba(0,0,0,0.1);
        }
        
        .header {
            text-align: center;
            margin-bottom: 30px;
            padding: 20px;
            background: linear-gradient(135deg, #667eea 0%, #764ba2 100%);
            color: white;
            border-radius: 10px;
        }
        
        .header h1 {
            font-size: 2.5em;
            margin-bottom: 10px;
        }
        
        .metadata {
            display: grid;
            grid-template-columns: repeat(auto-fit, minmax(300px, 1fr));
            gap: 20px;
            margin-bottom: 30px;
        }
        
        .metadata-card {
            background: #f8f9fa;
            padding: 20px;
            border-radius: 8px;
            border-left: 4px solid #007bff;
        }
        
        .statistics {
            display: grid;
            grid-template-columns: repeat(auto-fit, minmax(200px, 1fr));
            gap: 20px;
            margin-bottom: 30px;
        }
        
        .stat-card {
            text-align: center;
            background: white;
            padding: 20px;
            border-radius: 8px;
            box-shadow: 0 2px 4px rgba(0,0,0,0.1);
            border-top: 3px solid #28a745;
        }
        
        .stat-number {
            font-size: 2em;
            font-weight: bold;
            color: #28a745;
        }
        
        .bom-tree {
            margin-bottom: 30px;
        }
        
        .bom-item {
            margin: 5px 0;
            padding: 10px;
            border-radius: 5px;
            background: white;
            border-left: 3px solid #ccc;
        }
        
        .bom-item.assembly {
            border-left-color: #007bff;
            background: #f8f9fa;
        }
        
        .bom-item.part {
            border-left-color: #28a745;
        }
        
        .bom-item-header {
            display: flex;
            justify-content: between;
            align-items: center;
            cursor: pointer;
        }
        
        .bom-item-info {
            display: flex;
            gap: 20px;
            align-items: center;
        }
        
        .part-thumbnail {
            width: 60px;
            height: 60px;
            object-fit: cover;
            border-radius: 4px;
            border: 1px solid #ddd;
        }
        
        .bom-children {
            margin-left: 30px;
            margin-top: 10px;
        }
        
        .properties-table {
            width: 100%;
            border-collapse: collapse;
            margin-top: 10px;
        }
        
        .properties-table th,
        .properties-table td {
            border: 1px solid #ddd;
            padding: 8px;
            text-align: left;
        }
        
        .properties-table th {
            background-color: #f2f2f2;
        }
        
        .footer {
            text-align: center;
            margin-top: 40px;
            padding: 20px;
            background: #f8f9fa;
            border-radius: 8px;
        }
        
        .collapsible {
            cursor: pointer;
        }
        
        .collapsible:before {
            content: "▼ ";
            display: inline-block;
            transition: transform 0.3s;
        }
        
        .collapsible.collapsed:before {
            transform: rotate(-90deg);
        }
        
        .collapsed + .bom-children {
            display: none;
        }
    </style>
    <script>
        function toggleCollapse(element) {
            element.classList.toggle('collapsed');
        }
        
        function expandAll() {
            document.querySelectorAll('.collapsible').forEach(el => el.classList.remove('collapsed'));
        }
        
        function collapseAll() {
            document.querySelectorAll('.collapsible').forEach(el => el.classList.add('collapsed'));
        }
    </script>
</head>
<body>
    <div class="container">
        {content}
    </div>
</body>
</html>
"""
        return html_template
    
    def format_file_size(self, size_bytes):
        """Dosya boyutunu formatla"""
        if size_bytes == 0:
            return "0 B"
        
        for unit in ['B', 'KB', 'MB', 'GB']:
            if size_bytes < 1024:
                return f"{size_bytes:.1f} {unit}"
            size_bytes /= 1024
        return f"{size_bytes:.1f} TB"
    
    def generate_header_section(self):
        """Header section oluştur"""
        metadata = self.bom_data.get('metadata', {})
        
        return f"""
        <div class="header">
            <h1>🔧 STEP BOM Analysis Report</h1>
            <p>Generated by STEP BOM Analyzer v3.0 - FreeCAD Native Edition</p>
        </div>
        """
    
    def generate_metadata_section(self):
        """Metadata section oluştur"""
        metadata = self.bom_data.get('metadata', {})
        file_info = self.bom_data.get('file_info', {})
        
        return f"""
        <div class="metadata">
            <div class="metadata-card">
                <h3>📁 File Information</h3>
                <p><strong>File Name:</strong> {file_info.get('file_name', 'Unknown')}</p>
                <p><strong>File Size:</strong> {self.format_file_size(file_info.get('file_size', 0))}</p>
                <p><strong>File Path:</strong> {file_info.get('file_path', 'Unknown')}</p>
            </div>
            <div class="metadata-card">
                <h3>⚙️ Processing Information</h3>
                <p><strong>Generated:</strong> {metadata.get('generation_date', 'Unknown')}</p>
                <p><strong>FreeCAD Version:</strong> {'.'.join(metadata.get('freecad_version', ['Unknown'])[:3])}</p>
                <p><strong>Document:</strong> {metadata.get('document_name', 'Unknown')}</p>
            </div>
        </div>
        """
    
    def generate_statistics_section(self):
        """Statistics section oluştur"""
        stats = self.bom_data.get('statistics', {})
        
        return f"""
        <div class="statistics">
            <div class="stat-card">
                <div class="stat-number">{stats.get('total_items', 0)}</div>
                <div>Total Items</div>
            </div>
            <div class="stat-card">
                <div class="stat-number">{stats.get('total_parts', 0)}</div>
                <div>Total Parts</div>
            </div>
            <div class="stat-card">
                <div class="stat-number">{stats.get('total_assemblies', 0)}</div>
                <div>Total Assemblies</div>
            </div>
            <div class="stat-card">
                <div class="stat-number">{stats.get('unique_parts', 0)}</div>
                <div>Unique Parts</div>
            </div>
            <div class="stat-card">
                <div class="stat-number">{stats.get('max_hierarchy_depth', 0)}</div>
                <div>Max Depth</div>
            </div>
        </div>
        """
    
    def generate_bom_tree_section(self):
        """BOM tree section oluştur"""
        bom_structure = self.bom_data.get('bom_structure', [])
        
        controls = """
        <div style="margin-bottom: 20px;">
            <button onclick="expandAll()" style="padding: 8px 16px; margin-right: 10px; background: #007bff; color: white; border: none; border-radius: 4px; cursor: pointer;">Expand All</button>
            <button onclick="collapseAll()" style="padding: 8px 16px; background: #6c757d; color: white; border: none; border-radius: 4px; cursor: pointer;">Collapse All</button>
        </div>
        """
        
        tree_html = "<div class='bom-tree'>" + controls
        tree_html += "<h2>📋 Hierarchical BOM Structure</h2>"
        
        for item in bom_structure:
            tree_html += self._generate_bom_item_html(item, level=0)
        
        tree_html += "</div>"
        
        return tree_html
    
    def _generate_bom_item_html(self, item, level=0):
        """BOM item için HTML oluştur"""
        indent = "  " * level
        item_type = item.get('item_type', 'Part').lower()
        
        # Thumbnail image
        thumbnail_html = ""
        if item.get('name') in self.part_images:
            img_path = self.part_images[item['name']].get('iso', {}).get('path', '')
            if img_path and os.path.exists(img_path):
                # Relative path'e çevir
                rel_path = os.path.basename(img_path)
                thumbnail_html = f'<img src="{rel_path}" alt="{item.get("name", "")}" class="part-thumbnail">'
        
        # Properties table
        properties = [
            ("Name", item.get('name', '')),
            ("Label", item.get('label', '')),
            ("Type", item.get('type_id', '')),
            ("Quantity", item.get('quantity', 1)),
            ("Volume", f"{item.get('volume', 0):.2f} mm³"),
            ("Surface Area", f"{item.get('surface_area', 0):.2f} mm²"),
            ("Mass", f"{item.get('mass', 0):.3f} g")
        ]
        
        properties_html = "<table class='properties-table'>"
        for prop_name, prop_value in properties:
            properties_html += f"<tr><th>{prop_name}</th><td>{prop_value}</td></tr>"
        properties_html += "</table>"
        
        # Children
        children_html = ""
        children = item.get('children', [])
        if children:
            children_html = "<div class='bom-children'>"
            for child in children:
                children_html += self._generate_bom_item_html(child, level + 1)
            children_html += "</div>"
        
        # Collapsible header
        collapsible_class = "collapsible" if children else ""
        onclick = f'onclick="toggleCollapse(this)"' if children else ""
        
        item_html = f"""
        <div class="bom-item {item_type}">
            <div class="bom-item-header {collapsible_class}" {onclick}>
                <div class="bom-item-info">
                    {thumbnail_html}
                    <div>
                        <strong>{item.get('name', 'Unknown')}</strong>
                        <br><small>{item.get('label', '')}</small>
                        <br><small>Type: {item_type.title()} | Qty: {item.get('quantity', 1)}</small>
                    </div>
                </div>
            </div>
            <div style="margin-top: 10px;">
                {properties_html}
            </div>
            {children_html}
        </div>
        """
        
        return item_html
    
    def generate_html_report(self, output_path):
        """Complete HTML report oluştur"""
        try:
            # Template'i al
            template = self.generate_html_template()
            
            # Content sections oluştur
            content = ""
            content += self.generate_header_section()
            content += self.generate_metadata_section()
            content += self.generate_statistics_section() 
            content += self.generate_bom_tree_section()
            
            # Footer ekle
            content += f"""
            <div class="footer">
                <p>Report generated on {datetime.now().strftime('%Y-%m-%d %H:%M:%S')}</p>
                <p>STEP BOM Analyzer v3.0 - FreeCAD Native Edition</p>
                <p>ÜRTM Takip Ekibi</p>
            </div>
            """
            
            # Template'e content'i yerleştir
            html_content = template.format(content=content)
            
            # HTML dosyasını kaydet
            with open(output_path, 'w', encoding='utf-8') as f:
                f.write(html_content)
            
            log_message(f"HTML raporu oluşturuldu: {output_path}")
            return True
            
        except Exception as e:
            log_message(f"HTML rapor oluşturma hatası: {str(e)}", "ERROR")
            return False

class ExcelReportGenerator:
    """Excel BOM raporu oluşturucu (basit CSV alternatifi)"""
    
    def __init__(self, bom_data):
        self.bom_data = bom_data
    
    def generate_flat_bom_csv(self, output_path):
        """Flat BOM CSV oluştur"""
        try:
            with open(output_path, 'w', newline='', encoding='utf-8') as csvfile:
                writer = csv.writer(csvfile)
                
                # Header
                headers = [
                    'Level', 'Item_Type', 'Name', 'Label', 'Quantity', 
                    'Type_ID', 'Has_Geometry', 'Volume_mm3', 'Surface_Area_mm2', 'Mass_g',
                    'Length_mm', 'Width_mm', 'Height_mm', 'Parent_Name'
                ]
                writer.writerow(headers)
                
                # Data
                bom_structure = self.bom_data.get('bom_structure', [])
                self._write_bom_items_csv(writer, bom_structure)
            
            log_message(f"Excel BOM (CSV) oluşturuldu: {output_path}")
            return True
            
        except Exception as e:
            log_message(f"Excel BOM oluşturma hatası: {str(e)}", "ERROR")
            return False
    
    def _write_bom_items_csv(self, writer, items, parent_name=""):
        """BOM items'ları CSV'ye yaz"""
        for item in items:
            # Dimensions
            dims = item.get('dimensions', {})
            
            row = [
                item.get('level', 0),
                item.get('item_type', ''),
                item.get('name', ''),
                item.get('label', ''),
                item.get('quantity', 1),
                item.get('type_id', ''),
                item.get('has_geometry', False),
                item.get('volume', 0),
                item.get('surface_area', 0),
                item.get('mass', 0),
                dims.get('length', 0),
                dims.get('width', 0),
                dims.get('height', 0),
                parent_name
            ]
            
            writer.writerow(row)
            
            # Children
            children = item.get('children', [])
            if children:
                self._write_bom_items_csv(writer, children, item.get('name', ''))

def export_multi_format_reports(bom_data, part_images, output_dir, formats=None):
    """Multi-format export manager"""
    if formats is None:
        formats = ['html', 'csv', 'json']
    
    log_message("=" * 60)
    log_message("STEP BOM Analyzer - Multi-Format Export")
    log_message("=" * 60)
    
    try:
        # Output dizini oluştur
        os.makedirs(output_dir, exist_ok=True)
        
        export_results = {}
        
        # HTML Export
        if 'html' in formats:
            log_message("HTML raporu oluşturuluyor...")
            html_generator = HTMLReportGenerator(bom_data, part_images)
            html_path = os.path.join(output_dir, "bom_report.html")
            export_results['html'] = html_generator.generate_html_report(html_path)
        
        # CSV Export  
        if 'csv' in formats:
            log_message("Excel BOM (CSV) oluşturuluyor...")
            excel_generator = ExcelReportGenerator(bom_data)
            csv_path = os.path.join(output_dir, "bom_flat.csv")
            export_results['csv'] = excel_generator.generate_flat_bom_csv(csv_path)
        
        # JSON Export (raw data)
        if 'json' in formats:
            log_message("JSON raporu oluşturuluyor...")
            json_path = os.path.join(output_dir, "bom_complete.json")
            try:
                with open(json_path, 'w', encoding='utf-8') as f:
                    json.dump(bom_data, f, indent=2, ensure_ascii=False, default=str)
                export_results['json'] = True
                log_message(f"JSON raporu oluşturuldu: {json_path}")
            except Exception as e:
                log_message(f"JSON export hatası: {str(e)}", "ERROR")
                export_results['json'] = False
        
        # Sonuçları değerlendir
        successful_exports = sum(1 for success in export_results.values() if success)
        
        log_message("=" * 60)
        log_message("MULTI-FORMAT EXPORT COMPLETED!")
        log_message(f"📊 Başarılı export: {successful_exports}/{len(formats)}")
        log_message(f"📂 Output dizini: {output_dir}")
        log_message("=" * 60)
        
        return {
            "success": successful_exports > 0,
            "export_results": export_results,
            "successful_exports": successful_exports,
            "total_formats": len(formats)
        }
        
    except Exception as e:
        log_message(f"Multi-format export genel hatası: {str(e)}", "ERROR")
        return {"success": False, "error": str(e)}

# Ana macro fonksiyonu
def main():
    """Ana export manager fonksiyonu"""
    
    # Test parametreleri
    test_output_dir = r"C:\temp\bom_reports"
    test_formats = ['html', 'csv', 'json']
    
    # Parametreler (macro manager'dan gelecek)
    if 'MACRO_PARAMETERS' in globals():
        params = globals()['MACRO_PARAMETERS']
        output_dir = params.get('output_directory', test_output_dir)
        formats = params.get('export_formats', test_formats)
        bom_data = params.get('bom_data', {})
        part_images = params.get('part_images', {})
    else:
        output_dir = test_output_dir
        formats = test_formats
        bom_data = {"bom_structure": [], "metadata": {}, "statistics": {}}
        part_images = {}
        log_message("Test modunda çalışıyor - gerçek parametreleri bekliyor")
    
    # Multi-format export
    result = export_multi_format_reports(bom_data, part_images, output_dir, formats)
    
    # Sonucu yazdır
    if result["success"]:
        log_message("✅ Export Manager tamamlandı!")
        print("EXPORT_MANAGER_SUCCESS")
        print("EXPORT_MANAGER_DATA_START")
        print(json.dumps(result, indent=2, default=str))
        print("EXPORT_MANAGER_DATA_END")
    else:
        log_message(f"❌ Export Manager hatası: {result.get('error', 'Unknown error')}", "ERROR")
    
    return result

# FreeCAD Macro olarak çalıştırıldığında
if __name__ == "__main__":
    main()
